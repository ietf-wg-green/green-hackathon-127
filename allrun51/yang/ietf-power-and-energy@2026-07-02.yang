module ietf-power-and-energy {
  yang-version 1.1;
  
  namespace "urn:ietf:params:xml:ns:yang:ietf-power-and-energy";
  prefix eo;
  
  import ietf-hardware {
    prefix hw;
    reference
      "RFC 8348: A YANG Data Model for Hardware Management";
  }

  import iana-power-and-energy {
    prefix ianaeo;
    reference
      "IANA-defined identities for power and energy class";
  }

  organization
    "IETF GREEN Working Group";
  
  contact
    "WG Web: <https://datatracker.ietf.org/wg/green/>
     WG List: <mailto:green@ietf.org>";
     
     
  
  description
    "This YANG module specifies for Power and Energy monitoring and 
     control of devices within or connected to communication 
     networks.
     
     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.
     
     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXX
     (https://www.rfc-editor.org/info/rfcXXX); see the RFC itself
     for full legal notices.";

  revision 2026-07-02 {
    description
      "Initial revision";
    reference
      "RFC XXX: Energy Object YANG Data Model";
  }
  
  identity data-source-accuracy {
    description
      "Base identity for all possible data accuracy types.
       This identity serves as the root for a hierarchy of accuracy
       types, allowing for extensibility while maintaining alignment
       with current and future industry standards.

       The hierarchy, as defined in this YANG module, is as follows.
       Other modules may extend this hierarchy with additional
       accuracy base- and sub-types as needed.

       data-source-accuracy
        ??? accuracy-like-parent
        ??? accuracy-unknown
        ?    ??? accuracy-unavailable
        ??? accuracy-estimated
        ?    ??? accuracy-static
        ?    ??? accuracy-historic
        ?    ??? accuracy-learned
        ??? accuracy-measured
             ??? accuracy-measured-bronze
             ?    ??? accuracy-measured-bronze-1
             ?    ??? accuracy-measured-bronze-10
             ?    ??? accuracy-measured-bronze-100
             ?    ??? accuracy-measured-bronze-1000
             ??? accuracy-measured-silver
             ?    ??? accuracy-measured-silver-...
             ??? accuracy-measured-gold
             ?    ??? accuracy-measured-gold-...
             ??? accuracy-measured-red
             ?    ??? accuracy-measured-red-...
             ??? accuracy-measured-ones

       The accuracy levels under accuracy-measured are based on
       percent-wise accuracy classes:
          bronze:  +/- 30%
          silver:  +/- 10%
          gold:    +/- 5%
          red:     +/- 2%

       In addition, the accuracy-measured-ones identity indicates
       a power data measurement with all digits valid, except 
       trailing zeros.

       Since percent-wise accuracy works poorly for very small
       values, standards such as IEC 62053, IEC 61850-7-4 and
       IEEE 1451 define accuracy classes based on a combination of
       percent-wise accuracy and absolute accuracy thresholds.
       E.g. +/-1 % of reading  +  +/-0.05 absolute units.

       Similarly, for each percent-wise accuracy class, this module
       defines a few absolute tolerance classes, indicated by
       suffixes to the accuracy identity names. The suffixes indicate
       absolute accuracy thresholds:
          no suffix:   +/-0.5  absolute units
          -1:          +/-1    absolute unit
          -10:         +/-10   absolute units
          -100:        +/-100  absolute units
          -1000:       +/-1000 absolute units
       Thus, for example, accuracy-measured-gold-10 indicates
       a power data measurement with an accuracy of either
       +/-5% or +/-10 absolute units, whichever is larger.

       For example, a power sensor reading might report a value
       of 16250 milliwatts, under accuracy-measured-gold-10. This 
       indicates that the actual power value is between 15437.5 and 
       17062.5 milliwatts, since 5% of 16250 milliwatts is 812.5 
       milliwatts, which is greater than the absolute threshold of 
       10 milliwatts.

       At another time, the same sensor might report a value
       of 150 milliwatts, under accuracy-measured-gold-10. This 
       indicates that the actual power value is between 140 and 160 
       milliwatts, since 5% of 150 milliwatts is only 7.5 millwatts, 
       which is less than the absolute threshold of 10 milliwatts.";
  }
  identity accuracy-unknown {
    base data-source-accuracy;
    description
      "The accuracy of the power data is unknown.";
  }
  identity accuracy-unavailable {
    base accuracy-unknown;
    description
      "A power data is not available for some reason, such as a 
       sensor failure or a component being powered off.";
  }
  identity accuracy-like-parent {
    base data-source-accuracy;
    description
      "The accuracy of the power/energy data is the same as this 
       energy object's parent object. This identity is useful for 
       hierarchical energy objects where child objects inherit the 
       accuracy characteristics.";
  }
  identity accuracy-estimated {
    base data-source-accuracy;
    description
      "The power data is estimated, perhaps based on a model,
       history or calculation rather than a direct measurement.";
  }
  identity accuracy-static {
    base accuracy-estimated;
    description
      "The power data is based on static data, such as manufacturer 
       specifications, datasheet of typical power values or nameplate 
       ratings, rather than real-time measurements.";
  }
  identity accuracy-historic {
    base accuracy-estimated;
    description
      "The power data is based on an historic measurement data for 
       this specific system and usage pattern.";
  }
  identity accuracy-learned {
    base accuracy-estimated;
    description
      "The power data is based on an machine learning model 
       prediction.";
  }
  identity accuracy-measured {
    base data-source-accuracy;
    description
      "The power data is a direct, real-time measurement from a 
       sensor.";
  }
  identity accuracy-measured-bronze {
    base accuracy-measured;
    description
      "The power data is a direct, real-time measurement
       from a sensor with precision and accuracy such that
       |actual-sensor| <= sensor * 30% OR |actual-sensor| <= 0.5";
  }
  identity accuracy-measured-bronze-1 {
    base accuracy-measured-bronze;
    description
      "The power data is a direct, real-time measurement
       from a sensor with precision and accuracy such that
       |actual-sensor| <= sensor * 30% OR |actual-sensor| <= 1";
  }  
  identity accuracy-measured-bronze-10 {
    base accuracy-measured-bronze;
    description
      "The power data is a direct, real-time measurement
       from a sensor with precision and accuracy such that
       |actual-sensor| <= sensor * 30% OR |actual-sensor| <= 10";
  }  
  identity accuracy-measured-bronze-100 {
    base accuracy-measured-bronze;
    description
      "The power data is a direct, real-time measurement
       from a sensor with precision and accuracy such that
       |actual-sensor| <= sensor * 30% OR |actual-sensor| <= 100";
  }  
  identity accuracy-measured-bronze-1000 {
    base accuracy-measured-bronze;
    description
      "The power data is a direct, real-time measurement
       from a sensor with precision and accuracy such that
       |actual-sensor| <= sensor * 30% OR |actual-sensor| <= 1000";
  }  
  identity accuracy-measured-silver {
    base accuracy-measured;
    description
      "The power data is a direct, real-time measurement
       from a sensor with precision and accuracy such that
       |actual-sensor| <= sensor * 10% OR |actual-sensor| <= 0.5";
  }  
  identity accuracy-measured-silver-1 {
    base accuracy-measured-silver;
    description
      "The power data is a direct, real-time measurement
       from a sensor with precision and accuracy such that
       |actual-sensor| <= sensor * 10% OR |actual-sensor| <= 1";
  }  
  identity accuracy-measured-silver-10 {
    base accuracy-measured-silver;
    description
      "The power data is a direct, real-time measurement
       from a sensor with precision and accuracy such that
       |actual-sensor| <= sensor * 10% OR |actual-sensor| <= 10";
  }  
  identity accuracy-measured-silver-100 {
    base accuracy-measured-silver;
    description
      "The power data is a direct, real-time measurement
       from a sensor with precision and accuracy such that
       |actual-sensor| <= sensor * 10% OR |actual-sensor| <= 100  ";
  }  
  identity accuracy-measured-silver-1000 {
    base accuracy-measured-silver;
    description
      "The power data is a direct, real-time measurement
       from a sensor with precision and accuracy such that
       |actual-sensor| <= sensor * 10% OR |actual-sensor| <= 1000";
  }  
  identity accuracy-measured-gold {
    base accuracy-measured;
    description
      "The power data is a direct, real-time measurement
       from a sensor with precision and accuracy such that
       |actual-sensor| <= sensor * 5% OR |actual-sensor| <= 0.5";
  }
  identity accuracy-measured-gold-1 {
    base accuracy-measured-gold;
    description
      "The power data is a direct, real-time measurement
       from a sensor with precision and accuracy such that
       |actual-sensor| <= sensor * 5% OR |actual-sensor| <= 1";
  }  
  identity accuracy-measured-gold-10 {
    base accuracy-measured-gold;
    description
      "The power data is a direct, real-time measurement
       from a sensor with precision and accuracy such that
       |actual-sensor| <= sensor * 5% OR |actual-sensor| <= 10";
  }  
  identity accuracy-measured-gold-100 {
    base accuracy-measured-gold;
    description
      "The power data is a direct, real-time measurement
       from a sensor with precision and accuracy such that
       |actual-sensor| <= sensor * 5% OR |actual-sensor| <= 100";
  }  
  identity accuracy-measured-gold-1000 {
    base accuracy-measured-gold;
    description
      "The power data is a direct, real-time measurement
       from a sensor with precision and accuracy such that
       |actual-sensor| <= sensor * 5% OR |actual-sensor| <= 1000";
  }  
  identity accuracy-measured-red {
    base accuracy-measured;
    description
      "The power data is a direct, real-time measurement
       from a sensor with precision and accuracy such that
       |actual-sensor| <= sensor * 2% OR |actual-sensor| <= 0.5";
  }
  identity accuracy-measured-red-1 {
    base accuracy-measured-red;
    description
      "The power data is a direct, real-time measurement
       from a sensor with precision and accuracy such that
       |actual-sensor| <= sensor * 2% OR |actual-sensor| <= 1";
  }  
  identity accuracy-measured-red-10 {
    base accuracy-measured-red;
    description
      "The power data is a direct, real-time measurement
       from a sensor with precision and accuracy such that
       |actual-sensor| <= sensor * 2% OR |actual-sensor| <= 10";
  }  
  identity accuracy-measured-red-100 {
    base accuracy-measured-red;
    description
      "The power data is a direct, real-time measurement
       from a sensor with precision and accuracy such that
       |actual-sensor| <= sensor * 2% OR |actual-sensor| <= 100";
  }  
  identity accuracy-measured-red-1000 {
    base accuracy-measured-red;
    description
      "The power data is a direct, real-time measurement
       from a sensor with precision and accuracy such that
       |actual-sensor| <= sensor * 2% OR |actual-sensor| <= 1000";
  }  
  identity accuracy-measured-ones {
    base accuracy-measured;
    description
      "The power data is a direct, real-time measurement from a 
       sensor with all digits valid, except trailing zeros.
       For example, a sensor reading of 12300 represents a sensor 
       value between 12250 and 12350.";
  }
  
  typedef power-factor {
    type uint8 {
      range "0 .. 100";
    }
    default 100;
    description
      "The percent value of the power factor measurement.
       Leaf often omitted, implying 100%.";
  }

  identity power-state {
    description
      "Base identity for all possible power states. This identity
       serves as the root for a hierarchy of power states, allowing
       for extensibility while maintaining alignment with the IANA
       Power State Set Registry.";
    reference
      "IANA: Power State Set Registry:
       https://www.iana.org/assignments/power-state-sets/";
  }
  identity power-state-on {
    base power-state;
    description "full power on.";
    reference
      "IANA: Power State Set Registry (ieee1621-power-state-set):
       https://www.iana.org/assignments/power-state-sets/power-state-sets.xhtml#ieee1621";
  }
  identity power-state-off {
    base power-state;
    description "power off.";
    reference
      "IANA: Power State Set Registry (ieee1621-power-state-set):
       https://www.iana.org/assignments/power-state-sets/power-state-sets.xhtml#ieee1621";
  }
  identity power-state-sleep {
    base power-state;
    description "low-power state.";
    reference
      "IANA: Power State Set Registry (ieee1621-power-state-set):
       https://www.iana.org/assignments/power-state-sets/power-state-sets.xhtml#ieee1621";
  }
  identity energy-relationship-type {
    description "Base identity for energy object relationships";
  }
  identity powered-by {
    base energy-relationship-type;
    description "Energy Object A is powered by Energy Object B";
  }
  identity powering {
    base energy-relationship-type;
    description "Energy Object A is powering Energy Object B";
  }
  identity metered-by {
    base energy-relationship-type;
    description "Energy Object A is metered by Energy Object B";
  }
  identity metering {
    base energy-relationship-type;
    description "Energy Object A is metering Energy Object B";
  }
  identity aggregated-by {
    base energy-relationship-type;
    description "Energy Object A is aggregated by Energy Object B";
  }
  identity aggregating {
    base energy-relationship-type;
    description "Energy Object A is aggregating Energy Object B";
  }
  identity enabled-by {
    base energy-relationship-type;
    description
      "Energy Object A is enabled by Energy Object B. B must be 
       operational for A to function correctly";
  }
  identity enabling {
    base energy-relationship-type;
    description
      "Energy Object A is enabling Energy Object B. A must be 
       operational for B to function correctly.
       The inverse relationship is 'enabled-by'.";
  }
  container energy-objects {
    config false;
    description
      "Energy objects container for power and energy attributes.";
    
    list energy-object {
      key "id";
      description
        "Power and energy entry for an energy object, indexed by 
         energy object id. Each entry contains the complete set of 
         power and energy attributes for a specific physical 
         component.";
        
      leaf id {
        type string;
        description
          "An identifier that uniquely identifies the energy object";
      }
      
      leaf source-component-id {
        type leafref {
          path "/hw:hardware/hw:component/hw:name";
        }
        description
          "Reference to the component name in the ietf-hardware 
           model. This leaf creates a direct semantic link between 
           the power/energy attributes and the physical component 
           they describe.";
        reference
          "RFC 8348: A YANG Data Model for Hardware Management";
      }

      container power {
        description
          "Container for power measurement attributes.";
        
        leaf instantaneous-power {
          type int64;
          units "mWatts";
          mandatory false;
          description
           "The power usage measurement for the energy object right 
            now. This value represents the instantaneous power 
            consumption of the component. This value is 
            specified in milliwatts (mW). Positive values 
            indicate power consumption, while negative values can 
            indicate power generation (e.g., for devices with 
            battery backup or renewable energy sources).";
        }
        
        leaf nameplate-power {
          type uint32;
          units "Watts";
          description
            "The nameplate power rating of an energy object. This is 
             the maximum power that the energy object is designed to 
             consume or produce, as specified by the manufacturer. 
             Essential for power budget calculations and capacity 
             planning.";
        }
        
        leaf data-source-accuracy {
          type identityref {
            base data-source-accuracy;
          }
          default accuracy-like-parent;
          description
            "The accuracy of the power data source. Indicates 
             whether the data source is a direct measurement, an 
             estimate, or unavailable and also the accuracy level of 
             the data source. By default, the accuracy is inherited 
             from the parent energy object, facilitating 
             hierarchical accuracy definitions without the need to 
             specify accuracy at every level. This metadata is 
             crucial for network management applications to assess 
             the reliability and accuracy of the power data.";
        }
        
        leaf power-factor {
          type power-factor;
          description
            "The percent value of the power factor measurement for 
             the energy object. This information is important for 
             understanding the electrical characteristics of the 
             energy object and for correctly interpreting the power 
             data.";
        }

        leaf measurement-local {
          type boolean;
          description
            "Indicates whether the power measurement is local (true) 
             or remote (false). A local measurement is taken 
             directly at the energy object, while a remote 
             measurement is collected from an external source. 
             This information can be useful for troubleshooting and 
             understanding the data source.";
        }
      }

      container energy {
        description
          "Container for energy measurement attributes.";
        
        leaf total-energy-consumed {
          type uint64;
          units "Watt-hours";
          description
           "The total cumulative energy consumed by the energy 
            object since the last reset. This value is specified as 
            milliwatt-hours (mWh). This value is useful for tracking 
            overall energy usage over time for billing, reporting, 
            or optimization purposes.";
        }
        
        leaf total-energy-delivered {
          type uint64;
          units "Watt-hours";
          description
           "The total cumulative energy delivered by the energy 
            object since the last reset. This value is specified as 
            milliwatt-hours (mWh). This value is relevant for energy 
            objects capable of generating power, such as those with 
            renewable energy sources or battery backup systems, or 
            capable of providing energy to other energy objects 
            (e.g., PoE switches).";
        }

        leaf data-source-accuracy {
          type identityref {
            base data-source-accuracy;
          }
          default accuracy-like-parent;
          description
            "The accuracy of the energy data source. Indicates 
             whether the data source is a direct measurement, 
             an estimate, or unavailable and also the accuracy 
             level of the data source. 
             By default, the accuracy is inherited from the parent 
             energy object, facilitating hierarchical accuracy 
             definitions without the need to specify accuracy at 
             every level. This metadata is crucial for network 
             management applications to assess the reliability and 
             accuracy of the energy data.";
        }
        leaf measurement-local {
          type boolean;
          description
            "Indicates whether the energy measurement is local 
             (true) or remote (false). A local measurement is taken 
             directly at the energy object, while a remote 
             measurement is collected from an external source. 
             This information can be useful for troubleshooting and 
             understanding the data source.";
        }
        leaf-list certifications {
          type identityref {
            base ianaeo:certification-type;
          }
          description
            "List of certifications applicable to this energy object. 
             If this list is empty, the energy object has no 
             certifications.";
        }    
      }
      container power-state {
        description
          "Container for Power state monitoring.";
        leaf oper {
          type identityref {
            base power-state;
          }
          description
            "The current operational Power State of this Component, 
             as reported by the device. The leaf reflects the actual 
             observed Power State.";
        }
      }

      list relationship {
        key "type";
        config false;
        description 
          "Relationships for this energy object.";
                
        leaf type {
          type identityref {
            base energy-relationship-type; 
            // powered-by, powering, metered-by, metering, etc.
          }
          description
            "The type of relationship this energy object has with 
             peer objects.";
        }
        
        list peer {
          key "id";
          description 
            "Multiple peers for this relationship type.";
          
          leaf id {
            type string;
            description 
              "This id specifies the Universally Unique Identifier 
               (UUID) of the peer (other) Energy Object that this 
               energy object is 
               powering/powered-by/metering/metered-by, etc. 
               If the network level UUID is not known,some other 
               locally unique identifier MAY be used, in conjunction 
               with human readable details.";
            reference
              "RFC 9562: Universally Unique IDentifiers (UUIDs)";
          }
          leaf details {
            type string;
            description 
              "Additional details about the relationship.";
          }
        }
      }
    }
  }
  
  container energy-control {
    description
      "Energy control configuration, mirroring monitored objects. 
       The operational tree ('list energy-object' in 
       /energy-objects) will typically contain a significantly 
       larger number of instances than the configuration tree here. 
       The configuration tree represents the administrator's intent 
       and is limited to explicitly provisioned entries.";
    container energy-objects {
      description
        "Configuration container for the list of administratively 
         provisioned energy objects.";
      list energy-object {
        key "id";
        description
          "Control entry for a specific energy object.";
        
        leaf id {
          type leafref {
          path "/energy-objects/energy-object/id";
          require-instance false;
        }
          description 
            "An identifier that uniquely identifies the energy 
             object.";
        }
        container power-state {
          description
            "Container for Power state management.";
          
          leaf admin {
            type identityref {
              base power-state;
            }
            description
              "The administratively requested Power State for this 
               Component. This leaf represents the management system 
               intended Power State. When the 'admin' and the 
               respective 'oper' YANG leaf values differ, a 
               transition toward the 'admin' power state is in 
               progress. Absence of a configured value indicates that 
               the Component operates at its default Power State.";
          }

          leaf oper {
            type leafref {
              path "/energy-objects/energy-object/power-state/oper";
              require-instance false;
            }
            description
              "The current operational Power State of this Component, 
               as reported by the device. 
               References the corresponding operational energy object 
               instance in the monitoring tree.";
          }
        }
      }
    }
  }
}
